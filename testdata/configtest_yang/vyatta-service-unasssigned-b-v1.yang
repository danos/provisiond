module vyatta-service-unassigned-b-v1 {
	namespace "urn:vyatta.com:test:vyatta-service-unassigned-b:1";
	prefix unassigned-b;

	import vyatta-service-first-v1 {
		prefix first;
	}

	import vyatta-service-unassigned-a-v1 {
		prefix unassigned-a;
	}

	organization "AT&T Inc.";
	revision 2017-02-28 {
		description "Unassigned (B) test schema for configd-schema";
	}

	augment /first:first/first:firstSubCont {
		container unassigned-b {
			leaf unassigned-b-leaf {
				type string;
			}
		}
	}

	augment /unassigned-a:unassigned-a-cont/unassigned-a:unassigned-a-subcont {
		container unassigned-b {
			leaf unassigned-b-leaf {
				type string;
			}
		}
	}
}
